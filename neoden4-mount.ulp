#usage "<b>Mounting data generator with panelization support \n"
		"for Neoden 4 PNP machine</b>\n"

real machine_pcb_min = 0.0;
real machine_pcb_max = 1500.0;

real pcb_size_x = 0;
real pcb_size_y = 0;
real pcb_theta = 0;
real rail_size = 0;
real origin_offset_x = 0;
real origin_offset_y = 0;
real rotated_origin_offset_x = 0;
real rotated_origin_offset_y = 0;
real machine_offset_x = 0;
real machine_offset_y = 0;
real step_offset_x = 0;
real step_offset_y = 0;
int count_x = 1;
int count_y = 1;

string components[];
int components_skip[];

int generate_cam = 0;
int onload_autocalculate = 1;

/*
 *  Functions
 */
int mod(int c, int m) {
	return c - (c / m * m);
}

void autocalculate() {
	// Get board size automatically as per: https://gist.github.com/itavero/8042433
	board(B) {
 		char firstPoint = 'y';
 		real x1;
 		real y1;
 		real x2;
 		real y2;

 		B.wires(W) {
 			if (W.layer == LAYER_DIMENSION) {
				// Wire is on dimension layer
				real wx1 = u2mm(W.x1);
				real wy1 = u2mm(W.y1);
				real wx2 = u2mm(W.x2);
				real wy2 = u2mm(W.y2);

				// Start point of wire
				if(firstPoint == 'y') {
					firstPoint = 'n';
					x1 = wx1;
					x2 = wx1;
					y1 = wy1;
					y2 = wy2;
				} else {
					if (wx1 > x1) {
						x1 = wx1;
					}
					if (wx1 < x2) {
						x2 = wx1;
					}
					if (wy1 > y1) {
						y1 = wy1;
					}
					if (wy1 < y2) {
						y2 = wy1;
					}
				}

				// End point of wire
				if (wx2 > x1) {
					x1 = wx2;
				}
				if (wx2 < x2) {
					x2 = wx2;
				}
				if (wy2 > y1) {
					y1 = wy2;
				}
				if (wy2 < y2) {
					y2 = wy2;
				}

			}
		}

		pcb_size_x = (x1 - x2);
		pcb_size_y = (y1 - y2);
	}
}

void generate_output() {
	board(B) {
		string csvFileName = dlgFileSave("Top - Save File", filesetext(B.name, "-top.csv"), "*.csv");
		if (csvFileName == "") {
			dlgMessageBox(":No filename provided!");
			dlgReject();
		} else {
			// Calculate the sin() and cos() of the pcb_theta.
			// This NEEDS to be converted to radians. sin() and cos() take radians, not degrees
			real pcb_theta_rad = pcb_theta * (PI / 180);
			real s_theta = sin(pcb_theta_rad);
			real c_theta = cos(pcb_theta_rad);

			// Calculate origin offset: find center of panelized board,
			// (maximum x distance) / 2 and (maximum y distance) / 2
			real max_x = (pcb_size_x * count_x) + (step_offset_x * (count_x - 1));
			real max_y = (pcb_size_y * count_y) + (step_offset_y * (count_y - 1));
			// Calculate size with rail [FIX]
			if(rail_size > 0 && pcb_theta == 0) {
				max_x = max_x + ((rail_size + step_offset_x) * 2);
			} else {
				max_y = max_y + ((rail_size + step_offset_y) * 2);
			}
			origin_offset_x = max_x / 2;
			origin_offset_y = max_y / 2;
			rotated_origin_offset_x = origin_offset_x;
			rotated_origin_offset_y = origin_offset_y;

			if(pcb_theta > 0) {
				rotated_origin_offset_x = abs((origin_offset_x * c_theta) - (origin_offset_y * s_theta));
				rotated_origin_offset_y = abs((origin_offset_x * s_theta) + (origin_offset_y * c_theta));
			}

			// CAM output array
			string cam_output[];

			int i = 0;

			output(csvFileName) {
				printf("Designator,Footprint,Mid X,Mid Y,Layer,Rotation,Comment\n");
				printf(",,,,,,\n");

				B.elements(E) {
					if(!components_skip[i]) {
						int place = 0;
						real angle = 0;
						real cx = 0.0;
						real cy = 0.0;
						real final_x = 0.0;
						real final_y = 0.0;
						real source_x = u2mm(E.x);
						real source_y = u2mm(E.y);

						// Test for a fiducial, if so, include it. Right now, very specific to Digital
						// Indigo's naming convention, since no pad is included in fiducial currently.
						int fiducial_pos = strxstr(E.package.name, "^FIDUCIAL", 0);
						if(fiducial_pos >= 0) {
							place = 1;
						} else {
							E.package.contacts(C) {
								if (C.smd && C.smd.layer == 1) {
									place = 1;
								}
							}
						}

						if (place) {
							real composite_angle = E.angle + pcb_theta;
							angle = mod(composite_angle, 360);

							// Loop on the Y dimension
							for(int j = 1; j <= count_y; ++j) {
								cy = ((step_offset_y * (j - 1)) + (source_y * j) + (pcb_size_y * (j - 1))) - origin_offset_y;

								// Add rail size (and additional offset) [FIX]
								if(rail_size > 0 && pcb_theta > 0) {
									cy = cy + rail_size + step_offset_y;
								}

								// Loop on the X dimension
								for(int k = 1; k <= count_x; ++k) {
									cx = ((step_offset_x * (k - 1)) + (source_x * k) + (pcb_size_x * (k - 1))) - origin_offset_x;

									// Add rail size (and additional offset) [FIX]
									if(rail_size > 0 && pcb_theta == 0) {
										cx = cx + rail_size + step_offset_x;
									}

									if(pcb_theta > 0) {
										final_x = ((cx * c_theta) - (cy * s_theta)) + rotated_origin_offset_x;
										final_y = ((cy * c_theta) + (cx * s_theta)) + rotated_origin_offset_y;
									} else {
										final_x = cx + rotated_origin_offset_x;
										final_y = cy + rotated_origin_offset_y;
									}

									final_x = final_x + machine_offset_x;
									final_y = final_y + machine_offset_y;

									printf("%s-X%uY%u,%s,%.2fmm,%.2fmm,T,%.0f,%s\n",
										E.name, k, j, E.package.name, final_x, final_y, angle, E.value);
								}
							}
						}
					}
					++i;
				}
			}

			if(generate_cam) {
				output(filesetext(csvFileName, ".cam")) {
					// CAM header
					printf("%%FSLAX25Y25*%%\n");	// Set precision: 2 left of decimal, 5 right
					printf("%%MOMM*%%\n");			// Set grid: metric
					printf("%%AD100C,0.5*%%\n");	// Set aperture: 100 with 0.5mm circle
					printf("D100*\n");				// Select aperture

					// CAM main
					for(int k = 0; k <= i; k++) {
						printf("%s", cam_output[k]);
					}

					// CAM nnd
					printf("M02*\n");
				}
			}
		}
	}
}

/*
 *  Main
 */
void main() {
	// Run some default stuff here
	if(onload_autocalculate) {
		autocalculate();
	}

	board(B) {
		dlgDialog("Machine Parameters (mm)") {
			dlgGridLayout {
				dlgCell(0, 0) {
					dlgGroup("Component Skip") {
						int i = 0;
						dlgVBoxLayout {
							B.elements(E) {
								components[i] = E.name;
								components_skip[i] = 0;
								dlgCheckBox(E.name, components_skip[i]);
								i++;
							}
							dlgStretch(1);
						}
					}
				}
				dlgCell(0, 1) {
					dlgVBoxLayout {
						dlgHBoxLayout {
							dlgGroup("PCB Dimensions (mm)") {
								dlgHBoxLayout {
									dlgLabel("X");
									dlgRealEdit(pcb_size_x, machine_pcb_min, machine_pcb_max);
									dlgLabel("Y");
									dlgRealEdit(pcb_size_y, machine_pcb_min, machine_pcb_max);
									dlgPushButton("Auto-calculate") {
										autocalculate();
									}
								}
							}
							dlgGroup("PCB Rotation") {
								dlgHBoxLayout {
									dlgLabel("Θ");
									dlgRealEdit(pcb_theta, 0.00, 360.00);
								}
							}
						}
						dlgSpacing(5);
						dlgHBoxLayout {
							dlgGroup("Rail Dimensions (mm)") {
								dlgHBoxLayout {
									dlgLabel("Width");
									dlgRealEdit(rail_size);
								}
							}
							dlgGroup("Machine Offsets (mm)") {
								dlgHBoxLayout {
									dlgLabel("X");
									dlgRealEdit(machine_offset_x);
									dlgLabel("Y");
									dlgRealEdit(machine_offset_y);
								}
							}
							dlgGroup("Step Offsets (mm)") {
								dlgHBoxLayout {
									dlgLabel("X");
									dlgRealEdit(step_offset_x);
									dlgLabel("Y");
									dlgRealEdit(step_offset_y);
								}
							}
						}
						dlgSpacing(5);
						dlgHBoxLayout {
							dlgGroup("PCB Count") {
								dlgHBoxLayout {
									dlgLabel("X");
									dlgIntEdit(count_x);
									dlgLabel("Y");
									dlgIntEdit(count_y);
								}
							}
						}
						/*
						dlgSpacing(5);
						dlgHBoxLayout {
							dlgGroup("PCB Verification") {
								dlgHBoxLayout {
									dlgCheckBox("Generate CAM", generate_cam);
									dlgStretch(1);
								}
							}
						}
						*/
					}
				}
				dlgCell(1, 0, 1, 1) {
					dlgHBoxLayout {
						dlgStretch(1);
						dlgPushButton("Cancel") {
							dlgReject();
						}
						dlgPushButton("+Generate") {
							generate_output();
							dlgAccept();
						}
					}
				}
			}
		};
	}
}
